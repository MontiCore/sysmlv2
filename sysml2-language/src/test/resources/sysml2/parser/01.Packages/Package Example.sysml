/* (c) https://github.com/MontiCore/monticore */
package 'Package Example' {
	private import ScalarValues::*;
	 
	block Automobile;
	
	block Car is Automobile;	                         
	
	private value type Torque is ISQ::TorqueValue;
}
