/* (c) https://github.com/MontiCore/monticore */
state def $ {}

part def $ {}

port def a$ {}

package _9$ {}

attribute def $$$ {}

action def $a$ {}

constraint def a$1 {true}

requirement def _$ {}
