/* (c) https://github.com/MontiCore/monticore */
state def a123{}

part def a222{}

port def a33{}

package aA4{}

attribute def aR5{}

action def aaaR{}

constraint def AB{true}

requirement def Ab{}
