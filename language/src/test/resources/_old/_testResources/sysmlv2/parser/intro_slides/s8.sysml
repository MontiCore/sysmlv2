package 'Documentation Example' {
  doc /* This is documentation of the owning
       * package.
       */
  part def Automobile {
    doc /* This is documentation of Automobile. */
  }

  alias Automobile as Car;

  import ISO::TorqueValue as Torque;
}
