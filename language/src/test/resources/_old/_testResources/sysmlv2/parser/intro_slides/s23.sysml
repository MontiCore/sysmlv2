connection def PressureSeat {
  end : TireBead[1];
  end : TireMountingRim[1];
}

part wheelHubAssembly : WheelHubAssembly {

  part wheel : WheelAssembly[1] {
    part t : Tire[1] {
      part bead : TireBead[2];
    }
    part w: Wheel[1] {
      part rim : TireMountingRim[2];
      part mountingHoles : LugBoltMountingHole[5];
    }
    connection : PressureSeat connect t::bead to w::rim;
  }

  part lugBoltJoints : LugBoltJoint[0..5];
  part hub : Hub[1] {
    part h : LugBoltThreadableHole[5];
  }
  connect lugBoltJoints[0..1]
      to mountingHole => wheel::w::mountingHoles[1];
  connect lugBoltJoints[0..1]
      to threadedHole => hub::h[1];
}
