part def Vehicle {
  part parts : VehiclePart[*];

  part eng : Engine subsets parts;
  part trans : Transmission subsets parts;
  part wheels : Wheel[4] :> parts;
}

abstract part def VehiclePart;
part def Engine :> VehiclePart;
part def Transmission :> VehiclePart;
part def Wheel :> VehiclePart;
