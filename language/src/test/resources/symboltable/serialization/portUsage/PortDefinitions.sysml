/* (c) https://github.com/MontiCore/monticore */
package PortDefinitions {
  port def BooleanInput {
    in attribute val : boolean;
  }

  port def BooleanOutput {
    out attribute val : boolean;
  }
}
