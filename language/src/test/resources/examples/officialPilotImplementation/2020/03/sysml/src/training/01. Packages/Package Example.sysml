/* (c) https://github.com/MontiCore/monticore */
package 'Package Example' {
	private import ScalarValues::*;
	 
	block Automobile;
	
	alias Automobile as Car;	                         
	
	private import ISQ::TorqueValue as Torque;
}
