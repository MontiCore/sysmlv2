package '7a1-Variant Configuration - General Concept-a' {

	action doX;
	action doY;

	part part1;
	part part2;
	part part3 {
		port p1;
	}
	part part4;
	part part5 {
		port p2;
		variation perform action doXorY {
			variant perform doX;
			variant perform doY;
		}
	}
	part part6;

	abstract part def SubsystemA {
		abstract part :>> part3[0..1];
	}

	abstract part def SubsystemB {
		abstract part :>> part5[1];
	}

	part anyVehicleConfig {

		variation part subsystemA : SubsystemA {
			variant part subsystem1 : SubsystemA {
				part :>> part1[1];
				part :>> part2[1];
			}
			variant part subsystem2 : SubsystemA {
				part :>> part2[1];
				part :>> part3[1];
			}
		}

		variation part subsystemB : SubsystemB {
			variant part subsystem3 : SubsystemB {
				part :>> part4[1];
				part :>> part5[1];
			}
			variant part subsystem4 : SubsystemB {
				part :>> part5[1];
				part :>> part6[1];
			}
		}

		connect [0..1] subsystemA.part3.p1 to [1] subsystemB.part5.p2;

		assert constraint {
			subsystemA != subsystemA.subsystem2 |
			subsystemB == subsystemB.subsystem3
		}

	}

	part vehicleConfigA :> anyVehicleConfig {
		part :>> subsystemA = subsystemA.subsystem1;
		part :>> subsystemB = subsystemB.subsystem3 {
			part :>> part5 {
				perform action :>> doXorY = doX;
			}
		}
	}

	part VehicleConfigB :> anyVehicleConfig {
		part :>> subsystemA = subsystemA.subsystem2;
		part :>> subsystemB = subsystemB.subsystem4 {
			part :>> part5 {
				perform action :>> doXorY = doY;
			}
		}
	}
}
