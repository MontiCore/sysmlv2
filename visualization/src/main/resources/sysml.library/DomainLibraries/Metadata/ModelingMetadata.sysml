/* (c) https://github.com/MontiCore/monticore */
standard library package ModelingMetadata {
	doc
	/*
	 * This package contains definitions of metadata generally useful for annotating models.
	 */

	private import Base::Anything;
	private import ScalarValues::String;
	private import RiskMetadata::Risk;

	enum def StatusKind {
		doc
		/*
		 * StatusKind enumerates the possible statuses of work on a model element.
		 */

		open {
			doc
			/*
			 * Status is open.
			 */
		}

		tbd {
			doc
			/*
			 * Status is to be determined.
			 */
		}

		tbr {
			doc
			/*
			 * Status is to be resolved.
			 */
		}

		tbc {
			doc
			/*
			 * Status is to be confirmed.
			 */
		}

		done {
			doc
			/*
			 * Status is done.
			 */
		}

		closed {
			doc
			/*
			 * Status is closed.
			 */
		}
	}

	metadata def StatusInfo {
		doc
		/*
		 * StatusInfo is used to annotate a model element with status information.
		 */

		attribute originator : String [0..1] {
			doc
			/*
			 * The originator of the annotated element.
			 */
		}

		attribute owner : String [0..1] {
			doc
			/*
			 * The current owner of the annotated element.
			 */
		}

		attribute status : StatusKind {
			doc
			/*
			 * The current status of work on the annotated element (required).
			 */
		}

		item risk : Risk [0..1] {
			doc
			/*
			 * An assessment of risk for the annotated element.
			 */
		}
	}

	metadata def Rationale {
		doc
		/*
		 * Rationale is used to explain a choice or other decision made related to the
		 * annotated element.
		 */

		attribute text : String {
			doc
			/*
			 * A textual description of the rationale (required).
			 */
		}

		ref explanation : Anything [0..1] {
			doc
			/*
			 * A reference to a feature that provides a formal explanation of the rationale.
			 * (For example, a trade study whose result explains the choice of a certain alternative).
			 */
		}
	}

	metadata def Issue {
		doc
		/*
		 * Issue is used to record some issue concerning the annotated element.
		 */

		attribute text : String {
		doc
		/*
		 * A textual description of the issue.
		 */
		}
	}

	metadata def <refinement> Refinement {
		doc
		/*
		 * Refinement is used to identify a dependency as modeling a refinement relationship.
		 * In such a relationship, the source elements of the relationship provide a more precise and/or
		 * accurate representation than the target elements.
		 */

		:>> annotatedElement : SysML::Dependency;
	}

}
