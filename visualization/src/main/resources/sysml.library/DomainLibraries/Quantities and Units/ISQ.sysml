/* (c) https://github.com/MontiCore/monticore */
/standard library package ISQ {
     doc
     /*
      * International system of quantities (ISQ), as defined in ISO/IEC 80000
      */

 	private import ScalarValues::Real;
 	private import Quantities::*;
 	private import MeasurementReferences::*;

 	public import ISQBase::*;                  // ISO/IEC 80000 base quantities and general concepts
     public import ISQSpaceTime::*;             // ISO 80000-3 "Space and Time"
     public import ISQMechanics::*;             // ISO 80000-4 "Mechanics"
     public import ISQThermodynamics::*;        // ISO 80000-5 "Thermodynamics"
     public import ISQElectromagnetism::*;      // IEC 80000-6 "Electromagnetism"
     public import ISQLight::*;                 // ISO 80000-7 "Light"
     public import ISQAcoustics::*;             // ISO 80000-8 "Acoustics"
     public import ISQChemistryMolecular::*;    // ISO 80000-9 "Physical chemistry and molecular physics"
     public import ISQAtomicNuclear::*;         // ISO 80000-10 "Atomic and nuclear physics"
     public import ISQCharacteristicNumbers::*; // ISO 80000-11 "Characteristic numbers"
     public import ISQCondensedMatter::*;       // ISO 80000-12 "Condensed matter physics"
     public import ISQInformation::*;           // IEC 80000-13 "Information science and technology"

     /* Additional quantity declarations */

     attribute def TemperatureDifferenceValue :> ScalarQuantityValue {
         doc
         /*
          * temperature difference
          * A separate temperature difference quantity and unit are needed in order to support °C, °F and centrigrade temperature differences
          */
         attribute :>> num: Real;
         attribute :>> mRef: TemperatureDifferenceUnit[1];
     }

     attribute temperatureDifference: TemperatureDifferenceValue [*] nonunique :> scalarQuantities;

     attribute def TemperatureDifferenceUnit :> SimpleUnit {
         private attribute thermodynamicTemperaturePF: QuantityPowerFactor[1] { :>> quantity = isq.'Θ'; :>> exponent = 1; }
         attribute :>> quantityDimension { :>> quantityPowerFactors = thermodynamicTemperaturePF; }
     }
 }
