abstract part def Vehicle;
part def HumanDrivenVehicle specializes Vehicle {
  ref part driver : Person;
}

part def PoweredVehicle :> Vehicle {
  part eng : Engine;
}

part def HumanDrivenPoweredVehicle :> HumanDrivenVehicle, PoweredVehicle;
part def Engine;
part def Person;
