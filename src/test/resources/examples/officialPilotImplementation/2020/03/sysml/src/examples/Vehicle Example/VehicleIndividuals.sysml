/* (c) https://github.com/MontiCore/monticore */
package VehicleIndividuals {
	import VehicleUsages::*;
	import Time::DateTime;
	
	package IndividualDefinitions {

		/**
		 * This is an individual Vehicle with a mass of 1800 kg.
		 */
		individual def Vehicle1 :> Vehicle {
			value redefines mass = 1800@[kg];
		}
		
		/**
		 * This is an individual Vehicle with a mass of 1700 kg.
		 */
		individual def Vehicle2 :> Vehicle {
			value redefines mass = 1700@[kg];
		}
		
		individual def AxleAssembly1 :> AxleAssembly;
		
		individual def Wheel1 :> Wheel;
		individual def Wheel2 :> Wheel;
	}
	
	package IndividualSnapshots {
		import IndividualDefinitions::*;
	
		value t0: DateTime;
		value t1: DateTime;
		
		/**
		 * This is a snapshot of Vehicle1 at time t0;
		 */
		snapshot vehicle1_t0: Vehicle1 {
			// Note: Timestamping of snapshots is not yet formalized.
			value t = t0;
		}
		
		/**
		 * This is a time slice of Vehicle1 starting at snapshot vehicle1_t0 
		 * (time t0) and ending at time t1.
		 */
		timeslice vehicle1_t0_t1: Vehicle1 {
			snapshot :>> start = vehicle1_t0;
			snapshot :>> done {
				value t = t1;
			}
		}	
	}
	
	package IndividualConfigurations {
		import IndividualSnapshots::*;
	
		/** 
		 * This asserts that for some portion of its lifetime, Vehicle1 conforms
		 * to the configuration vehicle_C2;
		 */
		individual vehicle1_C2: Vehicle1 :> vehicle_C2;
		
		/**
		 * This is a snapshot of Vehicle1 in configuration vehicle1_C2 at time t0.
		 */
		snapshot vehicle1_C2_t0 :> vehicle1_C2, vehicle1_t0 {
			/**
			 * frontAxleAssembly is a feature of vehicle1_C2.
			 */
			snapshot axleAssembly1_t0: AxleAssembly1 :>> frontAxleAssembly {
				/**
				 * This asserts that Wheel1 is the leftFrontWheel of vehicle_C2_t0
				 * (leftFrontWheel is a feature of vehicle_C2::frontAxleAssembly).
				 */
				snapshot leftFrontWheel_t0: Wheel1 :>> leftFrontWheel;
			}
		}
		
		/**
		 * This is a snapshot of Vehicle1 in configuration vehicle_C2 at time t1.
		 */
		snapshot vehicle1_C2_t1 :> vehicle1_C2, vehicle1_t0_t1::done {
			snapshot axleAssembly1_t1: AxleAssembly1 :>> frontAxleAssembly {
				/**
				 * This asserts that Wheel1 is the rightFrontWheel of vehicle_C2_t1.
				 */
				snapshot rightFrontWheel_t1: Wheel1 :>> rightFrontWheel;
			}
		}	
	}
}
