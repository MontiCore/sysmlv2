/* (c) https://github.com/MontiCore/monticore */
package 'State Decomposition-1' {
	
	value type VehicleStartSignal;
	value type VehicleOnSignal;
	value type VehicleOffSignal;
	
	state def VehicleStates;
		
	state vehicleStates : VehicleStates {
		
		state operationalStates {
			entry; then off;
			
			state off;
			accept VehicleStartSignal 
				then starting;
				
			state starting;
			accept VehicleOnSignal
				then on;
				
			state on;
			accept VehicleOffSignal
				then off;
		}
		
		state healthStates { 
			/* ... */
		}
	}
	
}
