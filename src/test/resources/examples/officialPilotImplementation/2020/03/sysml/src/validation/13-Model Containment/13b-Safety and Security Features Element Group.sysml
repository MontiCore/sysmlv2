/* (c) https://github.com/MontiCore/monticore */
package '13b-Safety and Security Features Element Group' {
	
	part vehicle1_c1: '2-Parts Interconnection'::VehicleA {
		part interior {
			part alarm;
			part seatBelt[2];
			part frontSeat[2];
			part driverAirBag;
		}
		part bodyAssy {
			part body;
			part bumper;
			part keylessEntry;
		}
	}
	
	package 'Safety Features' {
		/* Parts that contribute to safety. */
		
		import vehicle1_c1::interior::seatBelt;
		import vehicle1_c1::interior::driverAirBag;
		import vehicle1_c1::bodyAssy::bumper;		
	}
	
	package 'Security Features' {
		/* Parts that contribute to security. */
		
		import vehicle1_c1::interior::alarm;
		import vehicle1_c1::bodyAssy::keylessEntry;
	}
	
	package 'Safety & Security Features' {
		/* Parts that contribute to safety AND
		 * parts that contribute to security.
		 */
		 
		import 'Safety Features'::*;
		import 'Security Features'::*;
	}
}
