/* (c) https://github.com/MontiCore/monticore */
package 'Symbol Definition2' {
  public import 'Symbol Definition';
  private import 'NoTransitivImport';
  private block VehiclePrivate;
  block BusPublic;
}
